module ietf-poweff-level-2 {
  yang-version 1.1;
  namespace "urn:ietf:params:xml:ns:yang:ietf-poweff-level-2";
  prefix ietf-poweff-level-2;

  import ietf-yang-types {
    prefix yang;
  }
  import ietf-poweff-types {
    prefix ietf-poweff-types;
  }
  import ietf-poweff-level-1 {
    prefix ietf-poweff-level-1;
  }

  organization
    "IETF GREEN (Getting Ready for Energy Efficient Networking)
     Working Group";
  contact
    "WG Web:   <https://datatracker.ietf.org/wg/green/>
     WG List:  <mailto:green@ietf.org>
     Editor:  Jan Lindblad
              <mailto:jan.lindblad+ietf@for.eco>
     Editor:  Snezana Mitrovic
              <mailto:snmitrov@cisco.com>
     Editor:  Marisol Palmero
              <mailto:mpalmero@cisco.com>";
  description
    "This YANG module defines the POWEFF Level 2.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.
      
    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.
    ";
  
  revision 2024-04-16 {
    description
      "Initial revision of POWEFF Level 2";
    reference
      "RFC XXXX: ...";
  }

  typedef subsys-name-t {
    type union {
      type enumeration {
        enum sys {
          description "The name of the top level object is 'sys'.";
        }
      }
      type string {
        pattern '[a-zA-Z]+[a-zA-Z0-9_/\.:-]*[a-zA-Z0-9_/]+';
      }
    }
    description 
      "Type for subsystem names. Must start with an ASCII
      alpabetic characters. The characters following may also be
      numeric characters, dash, underscore, forward slash. Parts of
      the name may be interpunctuated with a dot or colon. 
      Interpunctuation must not be the last character in the name.";
  }

  augment /ietf-poweff-level-1:poweff/ietf-poweff-level-1:stats {
    description 
      "Level 2 extends the Level 1 defintions with additional content.
      ";
    leaf device-total-energy-spent {
      type uint32;
      units J;
      ietf-poweff-types:sensor-type 
        ietf-poweff-types:st-w-j;
      ietf-poweff-types:tsdb-path 
        poweff.stats.device_total_energy_spent;
      description 
        "The total energy spent by the device since the point
        in time specified by ../device-total-energy-spent-since.
        This is the integral over time of the power draw as specified
        by ../ietf-poweff-level-1:device-current-total-power-draw.

        The energy used MUST be reported in Joule. The reported value 
        MUST NOT be lower than the actual energy used. 
        Any violations of these conditions
        may be legally construed as greenwashing, as defined by
        EU Green Claims Directive (GCD), EU 2023/0085(COD).";
    }
    leaf device-total-energy-spent-since {
      type yang:date-and-time;
      description 
        "The point in time at which the energy couting started.
        Typically at the most recent system initalization.";
    }
    list subsystem {
      key name;
      description 
        "List of subsystems, in a tree structure, as defined by the
        system implementor. There MUST be an entry called 'sys', 
        which MUST have a current-power-draw value equal to the 
        ../ietf-poweff-level-1:device-current-total-power-draw value.
        ";
      leaf name {
        type subsys-name-t;
        description 
          "The name of the subsystem. The name is built from the name
          of its ancestors joined with a dot (.). The root object of
          tree is called 'sys'.

          An example of a valid tree structure:
           - sys
           - sys.main-board
           - sys.main-board.cpu0
           - sys.main-board.cpu1
           - sys.linecard1
           - sys.linecard1.eth0/1
           - sys.psu0
           - sys.psu0.fan0
           - sys.psu0.fan1
          ";
      }
      leaf current-power-draw {
        type uint32;
        units W;
        ietf-poweff-types:sensor-type 
          ietf-poweff-types:st-p-in-true-watt;
        ietf-poweff-types:tsdb-path 
          poweff.stats.subsystem.current_power_draw;
        description 
          "Current power draw of the subsystem in Watts.
          This value MUST be larger than or equal to the sum of the
          power draw of all children listed in ../children, if any.";
      }
      leaf-list children {
        type leafref {
          path ../../subsystem/name;
        }
        description 
          "Children of this subsystem, each contributing to the power
          draw of this subsystem.";
      }
    }
  }
}
