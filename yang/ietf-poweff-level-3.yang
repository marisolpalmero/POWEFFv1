module ietf-poweff-level-3 {
  yang-version 1.1;
  namespace "urn:ietf:params:xml:ns:yang:ietf-poweff-level-3";
  prefix ietf-poweff-level-3;

  import ietf-poweff-types {
    prefix ietf-poweff-types;
  }
  import ietf-poweff-level-1 {
    prefix ietf-poweff-level-1;
  }
  import ietf-poweff-level-2 {
    prefix ietf-poweff-level-2;
  }

  organization
    "IETF GREEN (Getting Ready for Energy Efficient Networking)
     Working Group";
  contact
    "WG Web:   <https://datatracker.ietf.org/wg/green/>
     WG List:  <mailto:green@ietf.org>
     Editor:  Jan Lindblad
              <mailto:jan.lindblad+ietf@for.eco>
     Editor:  Snezana Mitrovic
              <mailto:snmitrov@cisco.com>
     Editor:  Marisol Palmero
              <mailto:mpalmero@cisco.com>";
  description
    "This YANG module defines the POWEFF Level 3.

    Copyright (c) 2024 IETF Trust and the persons identified as
    authors of the code.  All rights reserved.

    Redistribution and use in source and binary forms, with or
    without modification, is permitted pursuant to, and subject to
    the license terms contained in, the Revised BSD License set
    forth in Section 4.c of the IETF Trust's Legal Provisions
    Relating to IETF Documents
    (https://trustee.ietf.org/license-info).

    This version of this YANG module is part of RFC XXXX
    (https://www.rfc-editor.org/info/rfcXXXX); see the RFC itself
    for full legal notices.
      
    The key words 'MUST', 'MUST NOT', 'REQUIRED', 'SHALL',
    'SHALL NOT', 'SHOULD', 'SHOULD NOT', 'RECOMMENDED',
    'NOT RECOMMENDED', 'MAY', and 'OPTIONAL' in this document
    are to be interpreted as described in BCP 14 (RFC 2119)
    (RFC 8174) when, and only when, they appear in all
    capitals, as shown here.
    ";
  
  revision 2024-04-16 {
    description
      "Initial revision of POWEFF Level 3";
    reference
      "RFC XXXX: ...";
  }

  augment /ietf-poweff-level-1:poweff {
    description 
      "Level 3 extends the Level 1 & 2 defintions with additional
      content.
      ";
    container power-save {
      description 
        "Container for power-save control functions that the
        Network Controller may use to ask this Network Element
        to employ zero or more power-saving techniques.
        ";

      list subsystem {
        key name;
        description 
          "List of subsystems that offer power-saving functions.
          ";
        leaf name {
          type leafref {
            path "/ietf-poweff-level-1:poweff/" +
            "ietf-poweff-level-1:stats/"+
            "ietf-poweff-level-2:subsystem/"+
            "ietf-poweff-level-2:name";
            require-instance false;
          }
          description 
            "Name of the subsystem that offers power-saving
            functionality. This name normally matches one of the
            names in the poweff/stats subsystem list, but it is
            possible that a subsystem is not listed there e.g.
            because it has not started yet, during the system
            initialization.
            ";
        }
        choice selected-power-save-mode {
          description 
            "Choice of power saving modes that the Controller
            may select. Additional power-saving modes may be
            augmented into this choice by implementors, but may
            not be known/understood by the controller.
            ";
          leaf fully-powered {
            type empty;
            description 
              "The subsystem is fully powered, i.e. does not take
              any power-saving measures that would risk lowering the
              performance below normal levels.
              ";
          }
          leaf powered-off {
            type empty;
            description 
              "The subsystem is completely powered off, i.e. it is
              drawing no or little power while also delivering zero
              performance.
              ";
          }
          container napping {
            description 
              "The subsystem is napping, i.e. is taking frequent but
              brief pauses in the service it provides.
              ";
            leaf max-additional-latency {
              type ietf-poweff-types:microseconds;
              description 
                "Determines the maximum tolerated length of the pauses
                with reduced performance. This means the maximum 
                additional delay that this subsystem would incur on 
                e.g. detecting incoming traffic or performing its 
                function.
                ";
            }
          }
          container throttling {
            description 
              "The subsystem is throttling, i.e. is running with
              reduced capacity in the service it provides.
              ";
            leaf max-capacity-reduction {
              type ietf-poweff-types:percent;
              description 
                "Determines the maximum tolerated reduction of 
                performance. If this setting is applied to a bundle
                interface, for example, that consists of 3 underlaying
                links of equal capacity, and the controller sets the
                max-capacity-reduction value to 50%, the bundle
                interface could shut down one of the links.
                ";
            }
          }
        }
        leaf max-time-to-cancel-power-save {
          type ietf-poweff-types:microseconds;
          description 
            "The maximum time the Controller allows the subsystem
            to recover full performance. The subsystem should not
            engage in power-saving measures that take longer than
            this time to revert to full performance.
            ";
        }
        leaf estimated-power-reduction {
          type uint32;
          config false;
          description 
            "The subsystem's own estimate on how much of its own
            power draw that is reduced by the power-saving
            measures in effect.
            If the controller sets a bundle interface that consists of
            3 underlaying links of equal capacity, for example, into 
            50% throttling mode, the subsystem might shut down one of
            the underlaying links and report an 
            estimated-power-reduction of 33%.
            ";
        }
      }
    }
  }
}
