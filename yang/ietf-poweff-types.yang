module ietf-poweff-types {
  yang-version 1.1;
  namespace "urn:ietf:params:xml:ns:yang:ietf-poweff-types";
  prefix ietf-poweff-types;

  import ietf-tlm-philatelist-types {
    prefix ietf-tlm-philatelist-types;
  }

  organization
    "IETF GREEN (Getting Ready for Energy Efficient Networking)
     Working Group";
  contact
    "WG Web:   <https://datatracker.ietf.org/wg/green/>
     WG List:  <mailto:green@ietf.org>
     Editor:  Jan Lindblad
              <mailto:jan.lindblad+ietf@for.eco>
     Editor:  Snezana Mitrovic
              <mailto:snmitrov@cisco.com>
     Editor:  Marisol Palmero
              <mailto:mpalmero@cisco.com>";
  description
    "This YANG module defines basic quantities, measurement units
     and sensor types for the POWEFF framework.

     Copyright (c) 2021 IETF Trust and the persons identified as
     authors of the code. All rights reserved.

     Redistribution and use in source and binary forms, with or
     without modification, is permitted pursuant to, and subject to
     the license terms contained in, the Simplified BSD License set
     forth in Section 4.c of the IETF Trust's Legal Provisions  
  
     Relating to IETF Documents
     (https://trustee.ietf.org/license-info).

     This version of this YANG module is part of RFC XXXX
     (https://www.rfc-editor.org/info/rfcXXXX); see the RFC itself
     for full legal notices.";
  
  revision 2024-04-16 {
    description
      "Restructured to use the Telemetry Philatelist framework";
    reference
      "RFC XXXX: ...";
  }

  typedef something { 
    // FIXME: Used when we haven't decided the type yet
    type string;
    description "FIXME";
  }
  typedef xpath {
    type string; 
    // FIXME: Proper type needed
    description "FIXME";
  }
  typedef sample-frequency {
    type string; 
    // FIXME: Proper type needed
    description "FIXME";
  }

  // ========== SENSOR-QUANTITY ==============================
  identity sq-voltage {
    base ietf-tlm-philatelist-types:sensor-quantity;
    description 
      "Sensor reports electric tension, voltage.
      ";
  }
  identity sq-current {
    base ietf-tlm-philatelist-types:sensor-quantity;
    description 
      "Sensor reports electric current.
      ";
  }
  identity sq-power {
    base ietf-tlm-philatelist-types:sensor-quantity;
    description 
      "Sensor reports power draw (energy per unit of time).
      ";
  }
  identity sq-power-apparent {
    base sq-power;
    description 
      "Sensor reports apparent power, i.e. average electrical
      current times voltage (in VA).
      ";
  }
  identity sq-power-true {
    base sq-power;
    description 
      "Sensor reports true power, i.e. integral over current
      and voltage at each instant in time.
      ";
  }
  identity sq-energy {
    base ietf-tlm-philatelist-types:sensor-quantity;
    description 
      "Sensor reports actual energy drawn by asset.
      ";
  }
  identity sq-co2-emission {
    base ietf-tlm-philatelist-types:sensor-quantity;
    description 
      "Sensor reports CO2 (carbon dioxide) emission by asset.
      ";
  }
  identity sq-co2eq-emission {
    base ietf-tlm-philatelist-types:sensor-quantity;
    description 
      "Sensor reports CO2 (carbon dioxide) equivalent
      emission by asset.
      ";
  }
  identity sq-temperature {
    base ietf-tlm-philatelist-types:sensor-quantity;
    description 
      "Sensor reports temperature of asset.
      ";
  }
  identity sq-time {
    base ietf-tlm-philatelist-types:sensor-quantity;
    description 
    "Sensor reports time duration.
    ";
  }

  // ========== SENSOR-UNIT ==============================
  identity su-volt {
    base ietf-tlm-philatelist-types:sensor-unit;
    base sq-voltage;
    description 
    "Sensor unit volt, V.
    ";
  }
  identity su-ampere {
    base ietf-tlm-philatelist-types:sensor-unit;
    base sq-current;
    description 
      "Sensor unit ampere, A.
      ";
  }
  identity su-watt {
    base ietf-tlm-philatelist-types:sensor-unit;
    base sq-power;
    description 
      "Sensor unit watt, W.
      ";
  }
  identity su-voltampere {
    base ietf-tlm-philatelist-types:sensor-unit;
    base sq-power;
    description 
      "Sensor unit Volt*Ampere, VA.
      ";
  }
  identity su-kw {
    base ietf-tlm-philatelist-types:sensor-unit;
    base sq-power;
    description 
      "Sensor unit kilowatt, kW.
      ";
  }
  identity su-joule {
    base ietf-tlm-philatelist-types:sensor-unit;
    base sq-energy;
    description 
      "Sensor unit joule, J.
      ";
  }
  identity su-wh {
    base ietf-tlm-philatelist-types:sensor-unit;
    base sq-energy;
    description 
      "Sensor unit watthour, Wh.
      ";
  }
  identity su-kwh {
    base ietf-tlm-philatelist-types:sensor-unit;
    base sq-energy;
    description 
      "Sensor unit kliowatthour, kWh.
      ";
  }
  identity su-kelvin {
    base ietf-tlm-philatelist-types:sensor-unit;
    base sq-temperature;
    description 
      "Sensor unit kelvin, K.
      ";
  }
  identity su-celsius {
    base ietf-tlm-philatelist-types:sensor-unit;
    base sq-temperature;
    description 
      "Sensor unit celsius, C.
      ";
  }
  identity su-farenheit {
    base ietf-tlm-philatelist-types:sensor-unit;
    base sq-temperature;
    description 
      "Sensor unit farenheit, F.
      ";
  }
  identity su-gram {
    base ietf-tlm-philatelist-types:sensor-unit;
    base sq-co2-emission;
    description 
      "Sensor unit gram, g.
      ";
  }
  identity su-kg {
    base ietf-tlm-philatelist-types:sensor-unit;
    base sq-co2-emission;
    description 
      "Sensor unit kliogram, kg.
      ";
  }
  identity su-ton {
    base ietf-tlm-philatelist-types:sensor-unit;
    base sq-co2-emission;
    description 
      "Sensor unit ton, t.
      ";
  }
  identity su-second {
    base ietf-tlm-philatelist-types:sensor-unit;
    base sq-time;
    description 
      "Sensor unit second, s.
      ";
  }
  identity su-millisecond {
    base ietf-tlm-philatelist-types:sensor-unit;
    base sq-time;
    description 
      "Sensor unit millisecond, ms.
      ";
  }
  identity su-microsecond {
    base ietf-tlm-philatelist-types:sensor-unit;
    base sq-time;
    description 
      "Sensor unit microsecond, us.
      ";
  }

  // ========== SENSOR-TYPE ==============================
  extension sensor-type {
    argument identity-name;
    description 
      "YANG Extension used to declare which sensor type
      (as in input/output, quantity and unit) it has in a
      standardized machine readable way.
      See ietf-tlm-philatelist-types:sensor-type.
      ";
  }
  identity st-v-in {
    base ietf-tlm-philatelist-types:sensor-type;
    base ietf-tlm-philatelist-types:sc-input;
    base sq-voltage;
    base su-volt;
    description 
      "Sensor reporting Voltage In to asset.
      ";
  }
  identity st-v-out {
    base ietf-tlm-philatelist-types:sensor-type;
    base ietf-tlm-philatelist-types:sc-output;
    base sq-voltage;
    base su-volt;
    description 
      "Sensor reporting Voltage Out of asset.
      ";
  }
  identity st-i-in {
    base ietf-tlm-philatelist-types:sensor-type;
    base ietf-tlm-philatelist-types:sc-input;
    base sq-current;
    base su-ampere;
    description 
      "Sensor reporting Current In to asset.
      ";
  }
  identity st-i-out {
    base ietf-tlm-philatelist-types:sensor-type;
    base ietf-tlm-philatelist-types:sc-output;
    base sq-current;
    base su-ampere;
    description 
      "Sensor reporting Current Out of asset.
      ";
  }
  identity st-p-in-apparent-watt {
    base ietf-tlm-philatelist-types:sensor-type;
    base ietf-tlm-philatelist-types:sc-input;
    base sq-power-apparent;
    base su-voltampere;
    description 
      "Sensor reporting Power In to asset as apparent (I*U)
      power.
      ";
  }
  identity st-p-out-apparent-watt {
    base ietf-tlm-philatelist-types:sensor-type;
    base ietf-tlm-philatelist-types:sc-output;
    base sq-power-apparent;
    base su-voltampere;
    description 
      "Sensor reporting Power Out of asset as apparent (I*U)
      power.
      ";
  }
  identity st-p-in-true-watt {
    base ietf-tlm-philatelist-types:sensor-type;
    base ietf-tlm-philatelist-types:sc-input;
    base sq-power-true;
    base su-watt;
    description 
      "Sensor reporting Power In to asset as true power.
      ";
  }
  identity st-p-out-true-watt {
    base ietf-tlm-philatelist-types:sensor-type;
    base ietf-tlm-philatelist-types:sc-output;
    base sq-power-true;
    base su-watt;
    description 
      "Sensor reporting Power Out of asset as true power.
      ";
  }
  identity st-p-allocated-watt {
    base ietf-tlm-philatelist-types:sensor-type;
    base ietf-tlm-philatelist-types:sc-allocated;
    base sq-power;
    base su-watt;
    description 
      "Sensor reporting Allocated Power for asset.
      ";
  }
  identity st-w-j {
    base ietf-tlm-philatelist-types:sensor-type;
    base sq-energy;
    base su-joule;
    description 
      "Sensor reporting energy draw of asset in J.
      ";
  }
  identity st-w-wh {
    base ietf-tlm-philatelist-types:sensor-type;
    base sq-energy;
    base su-wh;
    description 
      "Sensor reporting energy draw of asset in Wh.
      ";
  }
  identity st-w-kwh {
    base ietf-tlm-philatelist-types:sensor-type;
    base sq-energy;
    base su-kwh;
    description 
      "Sensor reporting energy draw of asset in kWh.
      ";
  }
  identity st-t-k {
    base ietf-tlm-philatelist-types:sensor-type;
    base sq-temperature;
    base su-kelvin;
    description 
      "Sensor reporting Temperature of asset in K.
      ";
  }
  identity st-t-c {
    base ietf-tlm-philatelist-types:sensor-type;
    base sq-temperature;
    base su-celsius;
    description 
      "Sensor reporting Temperature of asset in °C.
      ";
  }
  identity st-t-f {
    base ietf-tlm-philatelist-types:sensor-type;
    base sq-temperature;
    base su-farenheit;
    description 
      "Sensor reporting Temperature of asset in °F.
      ";
  }

  // ========== TSDB-PATH ======================================
  extension tsdb-path {
    argument tsdb-path;
    description 
      "YANG Extension for declaring the TSDB path that a given
      YANG leaf would have.
      ";
  }
  // ========== COLLECTION-METHOD ==============================
  // None defined here

  // ========== POWER-SAVE UNITS ===============================
  typedef microseconds {
    type uint32;
    units us;
    description 
      "Time unit, millionths of a second. 10^-6 seconds.
      ";
  }
  typedef percent {
    type uint32 {
      range 0..100;
    }
    units %;
    description 
      "Percent fraction, 1/100 of something.
      ";
  }
}
